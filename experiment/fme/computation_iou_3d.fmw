FME workspace computation_iou_3d.fmw

Parameters:
- SourceDataset_CITYJSON = C:\Users\Florian\Data\city-to-scan-to-city\Experiments\experiment_test_case\01_input\9-276-556.city.json   # Source CityJSON File(s)
- DestDataset_CITYJSON = C:\Users\Florian\Data\city-to-scan-to-city\Experiments\experiment_test_case\05_reconstruction\scenario_000\output\model_fme_iou3d.json   # Destination CityJSON File
- COORDSYS = EPSG:7415   # COORDSYS Coordinate System
- CITYJSON_IN_LOD_1 = 2.2   # CityJSON Level of Detail to Read
- CITYJSON_IN_LOD_2 = 2.2   # CityJSON Level of Detail to Read
- SourceDataset_CITYJSON_5 = C:\Users\Florian\Data\city-to-scan-to-city\Experiments\experiment_test_case\05_reconstruction\scenario_000\output\model.json   # Source CityJSON File(s)
- SourceDataset_CITYJSON_6 = C:\Users\Florian\Data\city-to-scan-to-city\Experiments\experiment_test_case\01_input\9-276-556.city.json   # Source CityJSON File(s)
- SourceDataset_CITYJSON_7 = C:\Users\Florian\Data\city-to-scan-to-city\Experiments\experiment_test_case\05_reconstruction\scenario_000\output\model.json   # Source CityJSON File(s)

Readers:
- CITYJSON_1: CITYJSON from $(SourceDataset_CITYJSON) in $(COORDSYS)
- CITYJSON_2: CITYJSON from $(SourceDataset_CITYJSON_5) in $(COORDSYS)
- CITYJSON_3: CITYJSON from $(SourceDataset_CITYJSON_6) in $(COORDSYS)
- CITYJSON_4: CITYJSON from $(SourceDataset_CITYJSON_7) in $(COORDSYS)

Writers:
- CITYJSON_5: CITYJSON to $(DestDataset_CITYJSON) in $(COORDSYS)

Note: Reader for Building features with LOD setting "Highest"
Note: Reader for BuildingPart features with LOD setting as user parameter
Note: Reader for Building features with LOD setting "Highest"
Note: Aggregate all building parts per building
Aggregator_2
    ACCUM_ATTRS_NAME = Use Attributes From One Feature
    AGGREGATE_TYPE = Homogeneous Collection (If Possible)
    GROUP_BY = cityjson_parents{0}
    MODE = Geometry - Assemble One Level
    SEP = ,
    AGGREGATE -> FeatureJoiner [RIGHT]
Note: Join aggregated building geometries (keep right) to building attributes (left)
FeatureJoiner
    ATTR_CONFLICT_RES = Prefer Left
    GEOMETRY_HANDLING = Prefer Right
    JOIN_KEYS = fid cityjson_parents{0} AUTO
    JOIN_MODE = Inner
    JOINED -> FeatureJoiner_3 [LEFT]
Note: Reader for BuildingPart features with LOD setting as user parameter
Note: Aggregate all building parts per building
Aggregator
    ACCUM_ATTRS_NAME = Use Attributes From One Feature
    AGGREGATE_TYPE = Homogeneous Collection (If Possible)
    GROUP_BY = cityjson_parents{0}
    MODE = Geometry - Assemble One Level
    SEP = ,
    AGGREGATE -> FeatureJoiner_2 [RIGHT]
Note: Join aggregated building geometries (keep right) to building attributes (left)
FeatureJoiner_2
    ATTR_CONFLICT_RES = Prefer Left
    GEOMETRY_HANDLING = Prefer Right
    JOIN_KEYS = fid cityjson_parents{0} AUTO
    JOIN_MODE = Inner
    JOINED -> AttributeRenamer
Note: Ensure presence of an attribute named identically to the input model for matching: / Rename OGRLoader.identificatie to identificatie
AttributeRenamer
    ATTR_TABLE = RENAME_SET_DEFAULT OGRLoader.identificatie > identificatie
    KEEP_RENAMED_ONLY = no
    MISSING_INPUT_ATTRS = REMOVE
    -> FeatureJoiner_3 [RIGHT]
    -> Clipper [CANDIDATE]
    -> VolumeCalculator_3
Note: Filter out buildings from the input dataset that are not in the output dataset. Keep input geometry.
FeatureJoiner_3
    ATTR_CONFLICT_RES = Prefer Left
    GEOMETRY_HANDLING = Prefer Left
    JOIN_KEYS = identificatie identificatie AUTO
    JOIN_MODE = Inner
    JOINED -> Clipper [CLIPPER]
    JOINED -> VolumeCalculator_2
Note: Compute input building volume
VolumeCalculator_2
    MULT = 1
    SET_TRAIT = No
    VOLUME_ATTR = volume_input
    -> FeatureJoiner_5 [LEFT]
Note: Intersection
Clipper
    ADD_NODATA = YES
    BOUNDARY_CASES = INSIDE
    CLEANING_TOLERANCE = Automatic
    CLIPPED_ATTR = _clipped
    CONNECT_Z_MODE = SINGLE
    GENERATE_LIST = NO
    GROUP_BY = identificatie
    INVALID_PARTS_HANDLING = REJECT_WHOLE
    MISSING_M_MODE = Linear Interpolation
    MISSING_Z_MODE = Planar Interpolation
    MULTIPLE_CLIPPERS = NO
    M_VAL_SOURCE = CANDIDATE
    PRESERVE_RASTER_EXTENTS = NO
    RASTER_CELL_MODE = CENTER
    Z_VAL_SOURCE = CANDIDATE_AND_CLIPPER
    INSIDE -> VolumeCalculator
Note: Compute intersection volume
VolumeCalculator
    MULT = 1
    SET_TRAIT = No
    VOLUME_ATTR = volume_intersection
    -> FeatureJoiner_4 [LEFT]
Note: Compute reconstructed building volume
VolumeCalculator_3
    MULT = 1
    SET_TRAIT = No
    VOLUME_ATTR = volume_output
    -> FeatureJoiner_4 [RIGHT]
Note: Join intersection geometry (keep left) and intersection volume to output building attributes (keep right)
FeatureJoiner_4
    ATTR_CONFLICT_RES = Prefer Right
    GEOMETRY_HANDLING = Prefer Left
    JOIN_KEYS = identificatie identificatie AUTO
    JOIN_MODE = Inner
    JOINED -> FeatureJoiner_5 [RIGHT]
Note: Join input building volume from left, keep everything else from right
FeatureJoiner_5
    ATTR_CONFLICT_RES = Prefer Right
    GEOMETRY_HANDLING = Prefer Right
    JOIN_KEYS = identificatie identificatie AUTO
    JOIN_MODE = Inner
    JOINED -> AttributeCreator
Note: Compute IOU
Note: Write only Building features with volume attributes and IOU
AttributeCreator
    ATTR_TABLE = SET_TO IOU (real64) = @div(@Value(volume_intersection), @sub( @add(@Value(volume_input), @Value(volume_output)), @Value(volume_intersection) ) )
    -> Building (writer CITYJSON_5)

Bookmark: Input Building Models
Building (reader CITYJSON_3)
    attributes: b3_bouwlagen int32, fid string, b3_bag_bag_overlap real64, b3_dak_type string, b3_h_dak_50p real64, b3_h_dak_70p real64, b3_h_dak_max real64, b3_h_dak_min real64, b3_h_maaiveld real64, b3_kas_warenhuis logical, b3_mutatie_ahn3_ahn4 logical, b3_nodata_fractie_ahn3 real64, b3_nodata_fractie_ahn4 real64, b3_nodata_radius_ahn3 real64, b3_nodata_radius_ahn4 real64, b3_opp_buitenmuur real64, b3_opp_dak_plat real64, b3_opp_dak_schuin real64, b3_opp_grond real64, b3_opp_scheidingsmuur real64, b3_puntdichtheid_ahn3 real64, b3_puntdichtheid_ahn4 real64, b3_pw_bron string, b3_pw_datum int32, b3_pw_selectie_reden string, b3_reconstructie_onvolledig logical, b3_rmse_lod12 real64, b3_rmse_lod13 real64, b3_rmse_lod22 real64, b3_val3dity_lod12 string,
      b3_val3dity_lod13 string, b3_val3dity_lod22 string, b3_volume_lod12 real64, b3_volume_lod13 real64, b3_volume_lod22 real64, begingeldigheid string, documentdatum string, documentnummer string, geconstateerd logical, identificatie string, oorspronkelijkbouwjaar int32, status string, tijdstipregistratie string, tijdstipregistratielv string, voorkomenidentificatie int32
    -> FeatureJoiner [LEFT]
BuildingPart (reader CITYJSON_3)
    attributes: fid string
Metadata (reader CITYJSON_3)
    attributes: fullMetadataUrl string, geographicalExtent string, pointOfContact string, referenceSystem string, title string, version string

Bookmark: Input Building Models
Building (reader CITYJSON_1)
    attributes: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
BuildingPart (reader CITYJSON_1)
    attributes: fid string
    -> Aggregator_2
Metadata (reader CITYJSON_1)
    attributes: fullMetadataUrl string, geographicalExtent string, pointOfContact string, referenceSystem string, title string, version string

Bookmark: Reconstructed Building Models
Building (reader CITYJSON_4)
    attributes: OGRLoader.b3_bouwlagen real64, fid string, NestedFlowchart.PC2MeshQuality-LoD11.error_hist string, NestedFlowchart.SkipReplaceTester.replace logical, NestedFlowchart.SkipReplaceTester.skip logical, OGRLoader.b3_bag_bag_overlap real64, OGRLoader.b3_dak_type string, OGRLoader.b3_h_maaiveld real64, OGRLoader.b3_kas_warenhuis logical, OGRLoader.b3_kwaliteitsindicator logical, OGRLoader.b3_mutatie_ahn3_ahn4 logical, OGRLoader.b3_nodata_fractie_ahn3 real64, OGRLoader.b3_nodata_fractie_ahn4 real64, OGRLoader.b3_nodata_radius_ahn3 real64, OGRLoader.b3_nodata_radius_ahn4 real64, OGRLoader.b3_opp_buitenmuur real64, OGRLoader.b3_opp_dak_plat real64, OGRLoader.b3_opp_dak_schuin real64, OGRLoader.b3_opp_grond real64, OGRLoader.b3_opp_scheidingsmuur real64, OGRLoader.b3_puntdichtheid_ahn3 real64, OGRLoader.b3_puntdichtheid_ahn4 real64, OGRLoader.b3_pw_bron string, OGRLoader.b3_pw_datum real64, OGRLoader.b3_pw_selectie_reden string, OGRLoader.b3_reconstructie_onvolledig logical, OGRLoader.b3_rmse_lod12 real64, OGRLoader.b3_rmse_lod13 real64, OGRLoader.b3_rmse_lod22 real64, OGRLoader.b3_val3dity_lod12 string,
      OGRLoader.b3_val3dity_lod13 string, OGRLoader.b3_val3dity_lod22 string, OGRLoader.b3_volume_lod12 real64, OGRLoader.b3_volume_lod13 real64, OGRLoader.b3_volume_lod22 real64, OGRLoader.begingeldigheid string, OGRLoader.documentdatum string, OGRLoader.documentnummer string, OGRLoader.geconstateerd logical, OGRLoader.identificatie string, OGRLoader.oorspronkelijkbouwjaar real64, OGRLoader.status string, OGRLoader.tijdstipregistratie string, OGRLoader.tijdstipregistratielv string, OGRLoader.voorkomenidentificatie real64, h_50p real64, h_70p real64, h_ground real64, h_max real64, h_min real64, rms_lod12 real64, rms_lod13 real64, rms_lod22 real64, roof_type string, val3dity_codes_lod12 string, val3dity_codes_lod13 string, val3dity_codes_lod22 string
    -> FeatureJoiner_2 [LEFT]
BuildingPart (reader CITYJSON_4)
    attributes: fid string
Metadata (reader CITYJSON_4)
    attributes: geographicalExtent string, identifier string, pointOfContact string, referenceDate string, referenceSystem string, title string

Bookmark: Reconstructed Building Models
Building (reader CITYJSON_2)
    attributes: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
BuildingPart (reader CITYJSON_2)
    attributes: fid string
    -> Aggregator
Metadata (reader CITYJSON_2)
    attributes: geographicalExtent string, identifier string, pointOfContact string, referenceDate string, referenceSystem string, title string

Bookmark: CityJSON Writer
Building (writer CITYJSON_5)
    attributes: fid string, identificatie string, volume_input real64, volume_output real64, volume_intersection real64, IOU real64
BuildingPart (writer CITYJSON_5)
    attributes: fid string
Metadata (writer CITYJSON_5)
    attributes: geographicalExtent string, identifier string, pointOfContact string, referenceDate string, referenceSystem string, title string
