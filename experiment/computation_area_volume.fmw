FME workspace computation_area_volume.fmw

Parameters:
- SourceDataset_CITYJSON = C:\Users\Florian\Data\city-to-scan-to-city\Experiments\experiment_test_case\05_reconstruction\scenario_000\output\model.json   # Source CityJSON File(s)
- CITYJSON_IN_LOD_2 = 2.2   # CityJSON Level of Detail to Read
- SourceDataset_CITYJSON_2 = C:\Users\Florian\Data\city-to-scan-to-city\Experiments\experiment_test_case\05_reconstruction\scenario_000\output\model.json   # Source CityJSON File(s)
- COORDSYS_1 = EPSG:7415   # Coordinate System
- COORDSYS_2 = EPSG:7415   # Coordinate System
- DestDataset_CITYJSON = C:\Users\Florian\Data\city-to-scan-to-city\Experiments\experiment_test_case\05_reconstruction\scenario_000\output\model_volume.json   # Destination CityJSON File
- COORDSYS_3 = EPSG:7415   # Coordinate System

Readers:
- CITYJSON_1: CITYJSON from $(SourceDataset_CITYJSON) in $(COORDSYS_1)
- CITYJSON_3: CITYJSON from $(SourceDataset_CITYJSON_2) in $(COORDSYS_2)

Writers:
- CITYJSON_2: CITYJSON to $(DestDataset_CITYJSON) in $(COORDSYS_3)

VolumeCalculator
    MULT = 1
    SET_TRAIT = No
    VOLUME_ATTR = fme_volume
    -> AreaCalculator
AreaCalculator
    AREA_ATTR = fme_area
    AREA_TYPE = Plane Area
    MULT = 1
    -> Aggregator
Note: Aggregate building parts
Aggregator
    ACCUM_ATTRS_NAME = Use Attributes From One Feature
    AGGREGATE_TYPE = Homogeneous Collection (If Possible)
    COUNT_ATTR = n_building_parts
    GROUP_BY = cityjson_parents{0}
    MODE = Geometry - Assemble One Level
    SEP = ,
    SUM = fme_area fme_volume
    AGGREGATE -> FeatureJoiner [RIGHT]
FeatureJoiner
    ATTR_CONFLICT_RES = Prefer Left
    GEOMETRY_HANDLING = Prefer Left
    JOIN_KEYS = fid cityjson_parents{0} AUTO
    JOIN_MODE = Inner
    JOINED -> AttributeFilter
Note: Remove Buildings without BuildingPart, i.e., _volume == <null>
AttributeFilter
    ATTR_NAME = fme_volume
    ATTR_VALUES = <Empty>,<Missing>,<Null>,<Unfiltered>
    <UNFILTERED> -> Building (writer CITYJSON_2)
Building (writer CITYJSON_2)
    attributes: fid string, OGRLoader.identificatie string, fme_volume real64, fme_area real64, n_building_parts int32
BuildingPart (writer CITYJSON_2)
    attributes: fid string
Metadata (writer CITYJSON_2)
    attributes: geographicalExtent string, identifier string, pointOfContact string, referenceDate string, referenceSystem string, title string

Bookmark: Reader for Buildings
Note: Reader with LOD=Highest / Otherwise, Buildings are not read.
Building (reader CITYJSON_3)
    attributes: OGRLoader.b3_bouwlagen real64, fid string, NestedFlowchart.PC2MeshQuality-LoD11.error_hist string, NestedFlowchart.SkipReplaceTester.replace logical, NestedFlowchart.SkipReplaceTester.skip logical, OGRLoader.b3_bag_bag_overlap real64, OGRLoader.b3_dak_type string, OGRLoader.b3_h_maaiveld real64, OGRLoader.b3_kas_warenhuis logical, OGRLoader.b3_kwaliteitsindicator logical, OGRLoader.b3_mutatie_ahn3_ahn4 logical, OGRLoader.b3_nodata_fractie_ahn3 real64, OGRLoader.b3_nodata_fractie_ahn4 real64, OGRLoader.b3_nodata_radius_ahn3 real64, OGRLoader.b3_nodata_radius_ahn4 real64, OGRLoader.b3_opp_buitenmuur real64, OGRLoader.b3_opp_dak_plat real64, OGRLoader.b3_opp_dak_schuin real64, OGRLoader.b3_opp_grond real64, OGRLoader.b3_opp_scheidingsmuur real64, OGRLoader.b3_puntdichtheid_ahn3 real64, OGRLoader.b3_puntdichtheid_ahn4 real64, OGRLoader.b3_pw_bron string, OGRLoader.b3_pw_datum real64, OGRLoader.b3_pw_selectie_reden string, OGRLoader.b3_reconstructie_onvolledig logical, OGRLoader.b3_rmse_lod12 real64, OGRLoader.b3_rmse_lod13 real64, OGRLoader.b3_rmse_lod22 real64, OGRLoader.b3_val3dity_lod12 string,
      OGRLoader.b3_val3dity_lod13 string, OGRLoader.b3_val3dity_lod22 string, OGRLoader.b3_volume_lod12 real64, OGRLoader.b3_volume_lod13 real64, OGRLoader.b3_volume_lod22 real64, OGRLoader.begingeldigheid string, OGRLoader.documentdatum string, OGRLoader.documentnummer string, OGRLoader.geconstateerd logical, OGRLoader.identificatie string, OGRLoader.oorspronkelijkbouwjaar real64, OGRLoader.status string, OGRLoader.tijdstipregistratie string, OGRLoader.tijdstipregistratielv string, OGRLoader.voorkomenidentificatie real64, h_50p real64, h_70p real64, h_ground real64, h_max real64, h_min real64, rms_lod12 real64, rms_lod13 real64, rms_lod22 real64, roof_type string, val3dity_codes_lod12 string, val3dity_codes_lod13 string, val3dity_codes_lod22 string
    -> FeatureJoiner [LEFT]
BuildingPart (reader CITYJSON_3)
    attributes: fid string
Metadata (reader CITYJSON_3)
    attributes: geographicalExtent string, identifier string, pointOfContact string, referenceDate string, referenceSystem string, title string

Bookmark: Reader for BuildingParts
Note: Reader with LOD defined by user variable CITYJSON_IN_LOD
Building (reader CITYJSON_1)
    attributes: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
BuildingPart (reader CITYJSON_1)
    attributes: fid string
    -> VolumeCalculator
Metadata (reader CITYJSON_1)
    attributes: geographicalExtent string, identifier string, pointOfContact string, referenceDate string, referenceSystem string, title string
